module vxlan {
    namespace "urn:ietf:params:xml:ns:yang:ietf-vxlan";
    prefix "vxlan";

    import ietf-inet-types {
       prefix "inet";
    }

    /*import ietf-yang-types {
       prefix yang;
     }*/

    organization
      "IETF NVO3(Network Virtualization Overlays) Working Group";

      contact
       "
         editor:  <mailto:ccordes@snaproute.com>
        ";

    description
       "The YANG module defines a generic configuration
         model for VxLAN protocol";

    revision 2015-12-01 {
       description
         "02 revision.";
       reference
         "draft-chen-nvo3-vxlan-yang-02";
     }

    revision 2015-10-12 {
       description
         "01 revision.";
       reference
         "draft-chen-nvo3-vxlan-yang-01";
     }

    revision 2015-05-05 {
      description "Initial revision";
      reference
         "draft-chen-nvo3-vxlan-yang-00";
    }

    /* Typedefs  */

    typedef bgp-rt-type {
      type enumeration {
        enum import {
        description "For import";
       }
       enum export {
         description "For export";
       }
       enum both {
         description "For both import and export";
       }
     }
     description "BGP route-target type. Import from BGP YANG";
    }

    typedef vlan {
      type uint16 {
        range 1..4094;
      }
      description
      "Typedef for VLAN";
    }

    typedef vxlan-id {
      type uint32 {
         range 1..16777215;
      }
      description
        "Typedef for VxLAN ID.";
    }

    typedef access-type-vlan {
      type enumeration {
        enum access-type-vlan1to1 {
          description
            "Access type is VLAN 1:1.";
        }
        enum access-type-vlan1ton {
          description
            "Access type is VLAN 1:n.";
        }

      }
      default access-type-vlan1to1 ;
      description
        "VxLAN access type is VLAN.";
    }

    typedef access-type-mac {
       type empty ;
       description
         "VxLAN access type is MAC.";
    }

    typedef inner-vlan-handling-mode {
       type enumeration {
         enum discard-inner-vlan {
              description
                "Discard inner-VLAN.";
         }
         enum no-discard-inner-vlan {
              description
                "No discard inner-VLAN.";
         }
       }
       default discard-inner-vlan ;
       description
        "Typedef for inner-vlan-handling-mode";
    }

    typedef address-family-type {
       type enumeration {
         enum ipv4 {
           description
             "IPv4";
         }
         enum ipv6 {
           description
             "IPv6";
         }
       }
       description
         "Typedef for address family type.";
     }

    /* Configuration Data */

    container vxlan{
        list instance {
           key vni ;
		   config true;

           leaf vni {
             type vxlan-id;
             description
              "VNI domain";
           }

           leaf vlan-id {
            type vlan;
            config true;
            description
                "Vlan associated with the Access targets.  Used in conjunction with a given VTEP
                 inner-vlan-handling-mode";
           }
		  leaf-list IntfRefList {
			type string;
			config true;
			description
				"Host port interface reference, will be added as a member to the vxlan bridge vlan";
  		  }
		  leaf-list UntagIntfRefList {
			type string;
			config true;
			description
				"Host port interface reference for untagged, will be added as a member to the vxlan bridge vlan";
		  }
        }
        description
          "VxLAN instance.";

    container vtep {
            list instance {
			  key intf;
			  config true;

               leaf intf {
                  type string;
				  config true;
                  description
                     "VTEP instance identifier name. should be defined as either vtep<id#> or <id#> if the later then 'vtep' will be prepended to the <id#> example: vtep100 or 100";
                }

               leaf intf-ref {
                  type string;
				  config true;
                  description
                     "Source interface where the source ip will be derived from.  If an interface is not supplied the src-ip will be used.
					This attribute takes presedence over src-ip attribute.";
                }

                leaf dst-UDP {
                   type uint16;
                   config true;
                   default 4789;
                   description
                       "vxlan udp port.  Deafult is the iana default udp port";
                }
				
			   leaf TTL {
                    type uint16;
                    config true;
                    default 255;
                    description
                        "TTL of the Vxlan tunnel";
                }

                leaf TOS {
                    type uint16;
                    config true;
                    default 0;
                    description
                        "Type of Service";
                }

               leaf inner-vlan-handling-mode {
                  type inner-vlan-handling-mode;
				  config true;
                  description
                     "The inner vlan tag handling mode.";
                }

              leaf vni {
                type vxlan-id;
                config true;
                description
                   "Reference to the vxlan domain that this vtep is attached to";
              }

              leaf dst-ip {
                    type inet:ipv4-address;
                    config true;
                    description
                     "Destination IP address for the static VxLAN tunnel";
              }

              leaf src-ip {
                    type inet:ipv4-address;
                    config true;
				   default "0.0.0.0";
                    description
                     "Source IP address for the VxLAN tunnel, if this is supplied it is assumed that the intf-ref is this vtep.  This 
					attribute will be ignored if intf-ref is set";
              }

              leaf vlan-id {
                type uint16;
                config true;
                description
                    "Vlan Id to encapsulate with the vtep tunnel ethernet header";
              }
              leaf mtu {
	            type uint32;
	            config true;
	            default 1550;
	            description
	                "Set the MTU to be applied to all VTEP within this VxLAN";
	          }

            }
             description
                "VTEP instance.";
            }
     }

     // TODO add static binding for FDB entries
}
